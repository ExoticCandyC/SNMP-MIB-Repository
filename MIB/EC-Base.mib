--------------------------------------------------------------------------------
-- Copyright (C) 2021-2022  - Mohammad Kazem Azizollahi                       --
--                                                                            --
-- This program is free software: you can redistribute it and/or modify       --
-- it under the terms of the GNU General Public License as published by       --
-- the Free Software Foundation, either version 3 of the License, or any      --
-- later version.                                                             --
--                                                                            --
-- This program is distributed in the hope that it will be useful,            --
-- but WITHOUT ANY WARRANTY; without even the implied warranty of             --
-- MERCHANTABILITY or FITNESS FOR A PARTICULAR PURPOSE. See the               --
-- GNU General Public License for more details.                               --
--                                                                            --
-- You should have received a copy of the GNU General Public License          --
-- along with this program.  If not, see <http://www.gnu.org/licenses/>.      --
--                                                                            --
-- Only the public MIB files are under GNI GPL3 protection. The rest of this  --
-- project is the proprietary mental property of the developer, AKA           --
-- "Mohammad Kazem Azizollahi" and you are not allowed to distribute it       --
-- without a written letter of consent.                                       --
--------------------------------------------------------------------------------

--------------------------------------------------------------------------------
-- @Developer       https://github.com/ExoticCandyC                           --
-- @CreationDate    July 6th, 2022                                            --
-- @FileName        EC-Base.mib                                               --
-- @description     This file includes the basic definitions of the ASN.1     --
--                  data tree. Some of them are implemented in SNMPv2-MIB     --
--                  module but some MIB browsers don't have that module by    --
--                  default and manual intervention is required. So I just    --
--                  simply make all the definitions in this file and use      --
--                  this as a basis for all my SNMP enabled devices.          --
--------------------------------------------------------------------------------

EC-Base DEFINITIONS ::= BEGIN

--------------------------------------------------------------------------------
--------------------------------------------------------------------------------
--                               Import Section                               --
--------------------------------------------------------------------------------
--------------------------------------------------------------------------------

    -- The imports sections
    IMPORTS
        MODULE-IDENTITY,
        OBJECT-TYPE,
        NOTIFICATION-TYPE,
        TimeTicks
                FROM SNMPv2-SMI
        TEXTUAL-CONVENTION,
        TruthValue
                FROM SNMPv2-TC
        partyEntry,
        Party
                FROM SNMPv2-PARTY-MIB
    ;

--------------------------------------------------------------------------------
--------------------------------------------------------------------------------
--                       Generic Datatype Definitions                         --
--------------------------------------------------------------------------------
--------------------------------------------------------------------------------

    -- in network-byte order
    -- (this is a tagged type for historical reasons)
    IpAddress ::=
        [APPLICATION 0]
            IMPLICIT OCTET STRING (SIZE (4))

    -- this wraps
    Counter32 ::=
        [APPLICATION 1]
            IMPLICIT INTEGER (0..4294967295)

    -- this doesn't wrap
    Gauge32 ::=
        [APPLICATION 2]
            IMPLICIT INTEGER (0..4294967295)

    -- for backward-compatibility only
    Opaque ::=
        [APPLICATION 4]
            IMPLICIT OCTET STRING

    -- for counters that wrap in less than one hour with only 32 bits
    Counter64 ::=
        [APPLICATION 6]
            IMPLICIT INTEGER (0..18446744073709551615)

    -- Define the Float Textual Convention
    --   This definition was written by David Perkins.
    FLOAT ::= TEXTUAL-CONVENTION
        STATUS       current
        DESCRIPTION
            "A single precision floating-point number.  The semantics
             and encoding are identical for type 'single' defined in
             IEEE Standard for Binary Floating-Point,
             ANSI/IEEE Std 754-1985.
             The value is restricted to the BER serialization of
             the following ASN.1 type:
                 FLOATTYPE ::= [120] IMPLICIT FloatType
             (note: the value 120 is the sum of '30'h and '48'h)
             The BER serialization of the length for values of
             this type must use the definite length, short
             encoding form.

             For example, the BER serialization of value 123
             of type FLOATTYPE is '9f780442f60000'h.  (The tag
             is '9f78'h; the length is '04'h; and the value is
             '42f60000'h.) The BER serialization of value
             '9f780442f60000'h of data type Opaque is
             '44079f780442f60000'h. (The tag is '44'h; the length
             is '07'h; and the value is '9f780442f60000'h."
        SYNTAX      Opaque (SIZE (7))

    -- Define the UTCTime Textual Convention
    UTCTime ::= TEXTUAL-CONVENTION
        STATUS       current
        DESCRIPTION
            "format is YYMMDDHHMMZ or YYYYMMDDHHMMZ
               where: YY   - last two digits of year (only years
                             between 1900-1999)
                      YYYY - last four digits of the year (any year)
                      MM   - month (01 through 12)
                      DD   - day of month (01 through 31)
                      HH   - hours (00 through 23)
                      MM   - minutes (00 through 59)
                      Z    - denotes GMT (the ASCII character Z)
             For example, '9502192015Z' and '199502192015Z' represent
             8:15pm GMT on 19 February 1995. Years after 1999 must use
             the four digit year format. Years 1900-1999 may use the
             two or four digit format."
        SYNTAX      OCTET STRING (SIZE (11 | 13))

    -- Define the TIME-OF-DAY Textual Convention
    TIME-OF-DAY ::= TEXTUAL-CONVENTION
        STATUS       current
        DESCRIPTION
            "format is HHMMSS
               where: HH   - hours   (00 through 23)
                      MM   - minutes (00 through 59)
                      SS   - seconds (00 through 59)
             For example, '154523' represents 15:45:23.
             All the numebrs must be padded with 0 if they are less than 10.
             For exmaple, 13:2:0 is represented by '130200'."
        SYNTAX      OCTET STRING (SIZE (6))

    -- Define the DATE Textual Convention
    DATE ::= TEXTUAL-CONVENTION
        STATUS       current
        DESCRIPTION
            "format YYYYMMDD
               where: YYYY - year (any year)
                      MM   - month (01 through 12)
                      DD   - day of month (01 through 31)
             For example, '19950219' represents February 19th, 1995.
             Years must use the four digit year format."
        SYNTAX      OCTET STRING (SIZE (8))

    -- Define the TIME Textual Convention
    TIME ::= TEXTUAL-CONVENTION
        STATUS       current
        DESCRIPTION
            "format YYYY-MM-DDTHH:MM:SS+DH:DM or
                    YYYY-MM-DDTHH:MM:SS-DH:DM
               where: YYYY - year (any year)
                      MM   - month (1 through 12)
                      DD   - day of month (1 through 31)
                      HH   - hours   (0 through 23)
                      MM   - minutes (0 through 59)
                      SS   - seconds (0 through 59)
                      DH   - time zone hours offset (-13 through +13)
                      DM   - time zone minutes offset (0 or 30)
             For example, '2022-7-7T14:20:25+3:30' represents
             July 7th, 2022, 2:20:25 PM UTC+3:30. (Tehran Time Zone)
             No padding is required for this time format."
        SYNTAX      OCTET STRING (SIZE (2..25))

    DisplayString ::= TEXTUAL-CONVENTION
        STATUS       current
        DESCRIPTION
            "Represents textual information taken from the NVT ASCII
            character set, as defined in pages 4, 10-11 of RFC 854.
            To summarize RFC 854, the NVT ASCII repertoire specifies:
            - the use of character codes 0-127 (decimal)
            - the graphics characters (32-126) are interpreted as
            US ASCII
            - NUL, LF, CR, BEL, BS, HT, VT and FF have the special
            meanings specified in RFC 854
            - the other 25 codes have no standard interpretation
            - the sequence 'CR LF' means newline
            - the sequence 'CR NUL' means carriage-return
            - an 'LF' not preceded by a 'CR' means moving to the
            same column on the next line.
            - the sequence 'CR x' for any x other than LF or NUL is
            illegal.  (Note that this also means that a string may
            end with either 'CR LF' or 'CR NUL', but not with CR.)
            Any object defined using this syntax may not exceed 255
            characters in length."
        SYNTAX       OCTET STRING (SIZE (0..255))

    PhysAddress ::= TEXTUAL-CONVENTION
        STATUS       current
        DESCRIPTION
            "Represents media- or physical-level addresses."
        SYNTAX       OCTET STRING

    MacAddress ::= TEXTUAL-CONVENTION
        STATUS       current
        DESCRIPTION
            "Represents an 802 MAC address represented in the
            `canonical' order defined by IEEE 802.1a, i.e., as if it
            were transmitted least significant bit first, even though
            802.5 (in contrast to other 802.x protocols) requires MAC
            addresses to be transmitted most significant bit first."
        SYNTAX       OCTET STRING (SIZE (6))

    -- Define the Port number
    PortNumber ::= TEXTUAL-CONVENTION
        STATUS       current
        DESCRIPTION
            "An integer representing a port number. It is an unsigned 16bit
             integer, starting from 0 through 65535."
        SYNTAX      INTEGER (0..65535)

    -- Define the Phone number
    PhoneNumber ::= TEXTUAL-CONVENTION
        STATUS       current
        DESCRIPTION
            "Phone number in it's international form, or national form.
             E.G.
                +989121234567
                  09121234567
            "
        SYNTAX      OCTET STRING (SIZE (11..13))


--------------------------------------------------------------------------------
--------------------------------------------------------------------------------
--                          Generic OID Definitions                           --
--------------------------------------------------------------------------------
--------------------------------------------------------------------------------

    --member-body                 OBJECT IDENTIFIER ::= { iso             2 }
    org                         OBJECT IDENTIFIER ::= { iso             3 }
    dod                         OBJECT IDENTIFIER ::= { org             6 }
    internet                    OBJECT IDENTIFIER ::= { dod             1 }

    -- iso(1).org(3).dod(6).internet(1)
    --directory                   OBJECT IDENTIFIER ::= { internet        1 }
    mgmt                        OBJECT IDENTIFIER ::= { internet        2 }
    --experimental                OBJECT IDENTIFIER ::= { internet        3 }
    private                     OBJECT IDENTIFIER ::= { internet        4 }
    --security                    OBJECT IDENTIFIER ::= { internet        5 }
    snmpV2                      OBJECT IDENTIFIER ::= { internet        6 }
    --mail                        OBJECT IDENTIFIER ::= { internet        7 }
    --features                    OBJECT IDENTIFIER ::= { internet        8 }

    -- iso(1).org(3).dod(6).internet(1).mgmt(2)
    mib-2                       OBJECT IDENTIFIER ::= { mgmt            1 }

    -- iso(1).org(3).dod(6).internet(1).mgmt(2).mib-2(1)
    system                      OBJECT IDENTIFIER ::= { mib-2           1 }

    -- iso(1).org(3).dod(6).internet(1).mgmt(2).mib-2(1)
    interfaces                  OBJECT IDENTIFIER ::= { mib-2           2 }

    -- iso(1).org(3).dod(6).internet(1).mgmt(2).mib-2(1)
    snmp                        OBJECT IDENTIFIER ::= { mib-2          11 }

    -- iso(1).org(3).dod(6).internet(1).private(4)
    enterprises                 OBJECT IDENTIFIER ::= { private         1 }


--------------------------------------------------------------------------------
--------------------------------------------------------------------------------
--                        Personal Enterprise Number                          --
--------------------------------------------------------------------------------
--------------------------------------------------------------------------------

    -- iso(1).org(3).dod(6).internet(1).private(4).enterprises(1)
    -- This is my personal enterprise number officially assigned by:
    --      https://www.iana.org
    ExoticCandy-MIB             OBJECT IDENTIFIER ::= { enterprises 59097 }

--------------------------------------------------------------------------------
--------------------------------------------------------------------------------
--                         Enterprise MIB Structure                           --
--------------------------------------------------------------------------------
--------------------------------------------------------------------------------

    -- 1.3.6.internet(1).private(4).enterprises(1).ExoticCandy-MIB(59097)
    EC-General-Devices          OBJECT IDENTIFIER ::= { ExoticCandy-MIB 1 }

    -- 1.3.6.internet(1).private(4).enterprises(1).ExoticCandy-MIB(59097)
    EC-General-Software         OBJECT IDENTIFIER ::= { ExoticCandy-MIB 2 }

    -- 1.3.6.internet(1).private(4).enterprises(1).ExoticCandy-MIB(59097)
    EC-Generic-Traps            OBJECT IDENTIFIER ::= { ExoticCandy-MIB 3 }

    -- 1.3.6.internet(1).private(4).enterprises(1).ExoticCandy-MIB(59097)
    EC-Experimental             OBJECT IDENTIFIER ::= { ExoticCandy-MIB 4 }

    -- 1.3.6.internet(1).private(4).enterprises(1).ExoticCandy-MIB(59097)
    EC-Information              OBJECT IDENTIFIER ::= { ExoticCandy-MIB 5 }

    -- 1.3.6.internet(1).private(4).enterprises(1).ExoticCandy-MIB(59097)
    EC-Module-Identities        OBJECT IDENTIFIER ::= { ExoticCandy-MIB 6 }


--------------------------------------------------------------------------------
--------------------------------------------------------------------------------
--                               Trap Severity                                --
--------------------------------------------------------------------------------
--------------------------------------------------------------------------------

    Trap-Severity-Level OBJECT-TYPE
        SYNTAX  INTEGER
        {
            emergency     (0),      --system is unusable
            alert         (1),      --action must be taken immediately
            critical      (2),      --critical conditions
            error         (3),      --error conditions
            warning       (4),      --warning conditions
            notice        (5),      --normal but significant condition
            informational (6),      --informational messages
            debug         (7)       --debug-level messages
        }
        ACCESS  accessible-for-notify
        STATUS  mandatory
        DESCRIPTION
            "Severity level of the message"
        ::= { EC-Generic-Traps 1 }

--------------------------------------------------------------------------------
--------------------------------------------------------------------------------
--                              Module Identity                               --
--------------------------------------------------------------------------------
--------------------------------------------------------------------------------

    -- 1.3.6.1.4.enterprises(1).ExoticCandy-MIB(59097).EC-Module-Identities(5)
    EC-Base MODULE-IDENTITY
        LAST-UPDATED "202207060000Z"
        ORGANIZATION "Mohammad Kazem Azizollahi"
        CONTACT-INFO
                "GitHub:     https://github.com/ExoticCandyC
                 EMail:      mk.aziz.author@gmail.com
                "
        DESCRIPTION
                "The base MIB module for all of my SNMP enabled
                 project's MIB modules.

                 Copyright (C) 2021-2022 - Mohammad Kazem Azizollahi
                 This file is protected under GNU GPL 3 licence.
                ."
        REVISION     "202207060000Z"
        DESCRIPTION
                "Initial version created"
        ::= { EC-Module-Identities 1 }

--------------------------------------------------------------------------------
--------------------------------------------------------------------------------
--                         System information table                           --
--------------------------------------------------------------------------------
--------------------------------------------------------------------------------

    --iso(1).org(3).dod(6).internet(1).mgmt(2).mib-2(1).system(1)
    sysDescr OBJECT-TYPE
        SYNTAX      DisplayString (SIZE (0..255))
        MAX-ACCESS  read-only
        STATUS      current
        DESCRIPTION
            "A textual description of the entity.  This value should
            include the full name and version identification of
            the system's hardware type, software operating-system,
            and networking software."
        ::= { system 1 }

    --iso(1).org(3).dod(6).internet(1).mgmt(2).mib-2(1).system(1)
    sysObjectID OBJECT-TYPE
        SYNTAX      OBJECT IDENTIFIER
        MAX-ACCESS  read-only
        STATUS      current
        DESCRIPTION
            "The vendor's authoritative identification of the
            network management subsystem contained in the entity.
            This value is allocated within the SMI enterprises
            subtree (1.3.6.1.4.1) and provides an easy and
            unambiguous means for determining `what kind of box' is
            being managed.  For example, if vendor `Flintstones,
            Inc.' was assigned the subtree 1.3.6.1.4.1.424242,
            it could assign the identifier 1.3.6.1.4.1.424242.1.1
            to its `Fred Router'."
        ::= { system 2 }

    --iso(1).org(3).dod(6).internet(1).mgmt(2).mib-2(1).system(1)
    sysUpTime OBJECT-TYPE
        SYNTAX      TimeTicks
        MAX-ACCESS  read-only
        STATUS      current
        DESCRIPTION
            "The time (in hundredths of a second) since the
            network management portion of the system was last
            re-initialized."
        ::= { system 3 }

    --iso(1).org(3).dod(6).internet(1).mgmt(2).mib-2(1).system(1)
    sysContact OBJECT-TYPE
        SYNTAX      DisplayString (SIZE (0..255))
        MAX-ACCESS  read-write
        STATUS      current
        DESCRIPTION
            "The textual identification of the contact person for
            this managed node, together with information on how
            to contact this person.  If no contact information is
            known, the value is the zero-length string."
        ::= { system 4 }

    --iso(1).org(3).dod(6).internet(1).mgmt(2).mib-2(1).system(1)
    sysName OBJECT-TYPE
        SYNTAX      DisplayString (SIZE (0..255))
        MAX-ACCESS  read-write
        STATUS      current
        DESCRIPTION
            "An administratively-assigned name for this managed
            node.  By convention, this is the node's fully-qualified
            domain name.  If the name is unknown, the value is
            the zero-length string."
        ::= { system 5 }

    --iso(1).org(3).dod(6).internet(1).mgmt(2).mib-2(1).system(1)
    sysLocation OBJECT-TYPE
        SYNTAX      DisplayString (SIZE (0..255))
        MAX-ACCESS  read-write
        STATUS      current
        DESCRIPTION
            "The physical location of this node (e.g., 'telephone
            closet, 3rd floor').  If the location is unknown, the
            value is the zero-length string."
        ::= { system 6 }

    --iso(1).org(3).dod(6).internet(1).mgmt(2).mib-2(1).system(1)
    sysServices OBJECT-TYPE
        SYNTAX      INTEGER (0..127)
        MAX-ACCESS  read-only
        STATUS      current
        DESCRIPTION
            "A value which indicates the set of services that this
            entity may potentially offer.  The value is a sum.

            This sum initially takes the value zero. Then, for
            each layer, L, in the range 1 through 7, that this node
            performs transactions for, 2 raised to (L - 1) is added
            to the sum.  For example, a node which performs only
            routing functions would have a value of 4 (2^(3-1)).
            In contrast, a node which is a host offering application
            services would have a value of 72 (2^(4-1) + 2^(7-1)).
            Note that in the context of the Internet suite of
            protocols, values should be calculated accordingly:

                layer      functionality
                  1        physical (e.g., repeaters)
                  2        datalink/subnetwork (e.g., bridges)
                  3        internet (e.g., supports the IP)
                  4        end-to-end  (e.g., supports the TCP)
                  7        applications (e.g., supports the SMTP)

            For systems including OSI protocols, layers 5 and 6
            may also be counted."
        ::= { system 7 }

--------------------------------------------------------------------------------
--------------------------------------------------------------------------------
--                SNMP management - Authentication trap setting               --
--------------------------------------------------------------------------------
--------------------------------------------------------------------------------

    -- iso(1).org(3).dod(6).internet(1).mgmt(2).mib-2(1).snmp(11)
    snmpEnableAuthenTraps OBJECT-TYPE
        SYNTAX      INTEGER { enabled(1), disabled(2) }
        MAX-ACCESS  read-write
        STATUS      current
        DESCRIPTION
            "Indicates whether the SNMP entity is permitted to
            generate authenticationFailure traps.  The value of this
            object overrides any configuration information; as such,
            it provides a means whereby all authenticationFailure
            traps may be disabled.

            Note that it is strongly recommended that this object
            be stored in non-volatile memory so that it remains
            constant across re-initializations of the network
            management system."
        ::= { snmp       30 }

--------------------------------------------------------------------------------
--------------------------------------------------------------------------------
--                              SNMPv2 Modules                                --
--------------------------------------------------------------------------------
--------------------------------------------------------------------------------

    -- iso(1).org(3).dod(6).internet(1).snmpV2(6)
    snmpModules                 OBJECT IDENTIFIER ::= { snmpV2          3 }

    -- iso(1).org(3).dod(6).internet(1).snmpV2(6).snmpModules(3)
    snmpMIB                     OBJECT IDENTIFIER ::= { snmpModules     1 }

    -- iso(1).org(3).dod(6).internet(1).snmpV2(6).snmpModules(3).snmpMIB(1)
    snmpMIBObjects              OBJECT IDENTIFIER ::= { snmpMIB         1 }

--------------------------------------------------------------------------------
--------------------------------------------------------------------------------
--                           SNMP Trap Information                            --
--------------------------------------------------------------------------------
--------------------------------------------------------------------------------

    -- 1.3.6.1.snmpV2(6).snmpModules(3).snmpMIB(1).snmpMIBObjects(1)
    snmpTrap                    OBJECT IDENTIFIER ::= { snmpMIBObjects  4 }

    -- 1.3.6.1.6.snmpModules(3).snmpMIB(1).snmpMIBObjects(1).snmpTrap(4)
    snmpTrapOID OBJECT-TYPE
        SYNTAX OBJECT IDENTIFIER
        ACCESS not-accessible
        STATUS mandatory
        DESCRIPTION
            "The authoritative identification of the trap
            currently being sent.  This variable occurs as the
            second varbind of a SNMPv2-Trap-PDU."
        ::= { snmpTrap 1 }

    -- 1.3.6.1.6.snmpModules(3).snmpMIB(1).snmpMIBObjects(1).snmpTrap(4)
    snmpTrapTable OBJECT-TYPE
        SYNTAX     SEQUENCE OF SnmpTrapEntry
        MAX-ACCESS not-accessible
        STATUS     current
        DESCRIPTION
            "A table which keeps track of how many traps have
            been sent to each SNMPv2 entity."
        ::= { snmpTrap 2 }

    -- 1.3.6.1.6.snmpModules(3).snmpMIB(1).snmpMIBObjects(1).snmpTrap(4)
    snmpTrapEntry OBJECT-TYPE
        SYNTAX     SnmpTrapEntry
        MAX-ACCESS not-accessible
        STATUS     current
        DESCRIPTION
            "An entry which keeps track of how many traps have
            been sent to a particular SNMPv2 entity."
        AUGMENTS
        {
            partyEntry
        }
        ::= { snmpTrapTable 1 }

    SnmpTrapEntry ::= SEQUENCE
    {
        snmpTrapNumbers     Counter32
    }

    -- 1.3.6.1.6.snmpModules(3).snmpMIB(1).snmpMIBObjects(1).snmpTrap(4)
    snmpTrapEnterprise OBJECT-TYPE
        SYNTAX OBJECT IDENTIFIER
        ACCESS accessible-for-notify
        STATUS mandatory
        DESCRIPTION
            "The authoritative identification of the
            enterprise associated with the trap currently
            being sent.  When a SNMPv2 proxy agent is mapping
            an RFC1157 Trap-PDU into a SNMPv2-Trap-PDU, this
            variable occurs as the last varbind."
        ::= { snmpTrap 3 }

    -- 1.3.6.1.6.snmpModules(3).snmpMIB(1).snmpMIBObjects(1).snmpTrap(4)
    snmpV2EnableAuthenTraps OBJECT-TYPE
        SYNTAX TruthValue
        ACCESS read-write
        STATUS mandatory
        DESCRIPTION
            "Indicates whether the SNMPv2 entity, when acting
            in an agent role, is permitted to generate
            authenticationFailure traps.  The value of this
            object overrides any configuration information; as
            such, it provides a means whereby all
            authenticationFailure traps may be disabled.

            Note that it is strongly recommended that this
            object be stored in non-volatile memory so that it
            remains constant between re-initializations of the
            network management system."
        REFERENCE
            "Derived from RFC1213-MIB.snmpEnableAuthenTraps."
        ::= { snmpTrap 4 }

--------------------------------------------------------------------------------
--------------------------------------------------------------------------------
--                           SNMP Trap Collection                             --
--------------------------------------------------------------------------------
--------------------------------------------------------------------------------

    -- 1.3.6.1.snmpV2(6).snmpModules(3).snmpMIB(1).snmpMIBObjects(1)
    snmpTraps                   OBJECT IDENTIFIER ::= { snmpMIBObjects  5 }
    --snmpTraps OBJECT-TYPE
    --    SYNTAX      OBJECT IDENTIFIER
    --    ACCESS      not-accessible
    --    STATUS      current
    --    DESCRIPTION
    --        "The collection of the generic pre-defined SNMPv2 traps."
    --    ::= { snmpMIBObjects 5 }

    -- 1.3.6.1.6.snmpModules(3).snmpMIB(1).snmpMIBObjects(1).snmpTraps(5)
    coldStart NOTIFICATION-TYPE
        STATUS  current
        DESCRIPTION
            "A coldStart trap signifies that the SNMP entity,
            supporting a notification originator application, is
            reinitializing itself and that its configuration may
            have been altered."
        ::= { snmpTraps 1 }

    -- 1.3.6.1.6.snmpModules(3).snmpMIB(1).snmpMIBObjects(1).snmpTraps(5)
    warmStart NOTIFICATION-TYPE
        STATUS  current
        DESCRIPTION
            "A warmStart trap signifies that the SNMP entity,
            supporting a notification originator application,
            is reinitializing itself such that its configuration
            is unaltered."
        ::= { snmpTraps 2 }

    -- 1.3.6.1.6.snmpModules(3).snmpMIB(1).snmpMIBObjects(1).snmpTraps(5)
    linkDown NOTIFICATION-TYPE
        OBJECTS
        {
            ifIndex,
            ifAdminStatus,
            ifOperStatus
        }
        STATUS  current
        DESCRIPTION
            "A linkDown trap signifies that the SNMP entity, acting in
            an agent role, has detected that the ifOperStatus object for
            one of its communication links is about to enter the down
            state from some other state (but not from the notPresent
            state).  This other state is indicated by the included value
            of ifOperStatus."
        ::= { snmpTraps 3 }

    -- 1.3.6.1.6.snmpModules(3).snmpMIB(1).snmpMIBObjects(1).snmpTraps(5)
    linkUp NOTIFICATION-TYPE
        OBJECTS
        {
            ifIndex,
            ifAdminStatus,
            ifOperStatus
        }
        STATUS  current
        DESCRIPTION
            "A linkUp trap signifies that the SNMP entity, acting in an
            agent role, has detected that the ifOperStatus object for
            one of its communication links left the down state and
            transitioned into some other state (but not into the
            notPresent state).  This other state is indicated by the
            included value of ifOperStatus."
        ::= { snmpTraps 4 }

    -- 1.3.6.1.6.snmpModules(3).snmpMIB(1).snmpMIBObjects(1).snmpTraps(5)
    authenticationFailure NOTIFICATION-TYPE
        STATUS  current
        DESCRIPTION
            "An authenticationFailure trap signifies that the SNMP
            entity has received a protocol message that is not
            properly authenticated.  While all implementations
            of SNMP entities MAY be capable of generating this
            trap, the snmpEnableAuthenTraps object indicates
            whether this trap will be generated."
        ::= { snmpTraps 5 }

    -- 1.3.6.1.6.snmpModules(3).snmpMIB(1).snmpMIBObjects(1).snmpTraps(5)
    egpNeighborLoss NOTIFICATION-TYPE
        OBJECTS
        {
            egpNeighAddr
        }
        STATUS  current
        DESCRIPTION
            "An egpNeighborLoss trap signifies that an EGP
            neighbor has been marked down and the EGP peer
            relationship no longer obtains."
        ::= { snmpTraps 6 }


--------------------------------------------------------------------------------
--------------------------------------------------------------------------------
--                           The Interfaces Group                             --
--------------------------------------------------------------------------------
--------------------------------------------------------------------------------

    -- Implementation of the Interfaces group is mandatory for
    -- all systems.

    ifNumber OBJECT-TYPE
        SYNTAX  INTEGER
        ACCESS  read-only
        STATUS  mandatory
        DESCRIPTION
            "The number of network interfaces (regardless of
            their current state) present on this system."
        ::= { interfaces 1 }


    -- the Interfaces table

    -- The Interfaces table contains information on the entity's
    -- interfaces.  Each interface is thought of as being
    -- attached to a `subnetwork'.  Note that this term should
    -- not be confused with `subnet' which refers to an
    -- addressing partitioning scheme used in the Internet suite
    -- of protocols.

    ifTable OBJECT-TYPE
        SYNTAX  SEQUENCE OF IfEntry
        ACCESS  not-accessible
        STATUS  mandatory
        DESCRIPTION
            "A list of interface entries.  The number of
            entries is given by the value of ifNumber."
        ::= { interfaces 2 }

    ifEntry OBJECT-TYPE
        SYNTAX  IfEntry
        ACCESS  not-accessible
        STATUS  mandatory
        DESCRIPTION
            "An interface entry containing objects at the
            subnetwork layer and below for a particular
            interface."
        INDEX
        {
            ifIndex
        }
        ::= { ifTable 1 }

    IfEntry ::=
        SEQUENCE {
            ifIndex             INTEGER,
            ifDescr             DisplayString,
            ifType              INTEGER,
            ifMtu               INTEGER,
            ifSpeed             Gauge,
            ifPhysAddress       PhysAddress,
            ifAdminStatus       INTEGER,
            ifOperStatus        INTEGER,
            ifLastChange        TimeTicks,
            ifInOctets          Counter,
            ifInUcastPkts       Counter,
            ifInNUcastPkts      Counter,
            ifInDiscards        Counter,
            ifInErrors          Counter,
            ifInUnknownProtos   Counter,
            ifOutOctets         Counter,
            ifOutUcastPkts      Counter,
            ifOutNUcastPkts     Counter,
            ifOutDiscards       Counter,
            ifOutErrors         Counter,
            ifOutQLen           Gauge,
            ifSpecific          OBJECT IDENTIFIER
        }

    ifIndex OBJECT-TYPE
        SYNTAX  INTEGER
        ACCESS  read-only
        STATUS  mandatory
        DESCRIPTION
            "A unique value for each interface.  Its value
            ranges between 1 and the value of ifNumber.  The
            value for each interface must remain constant at
            least from one re-initialization of the entity's
            network management system to the next re-
            initialization."
        ::= { ifEntry 1 }

    ifDescr OBJECT-TYPE
        SYNTAX  DisplayString (SIZE (0..255))
        ACCESS  read-only
        STATUS  mandatory
        DESCRIPTION
            "A textual string containing information about the
            interface. This string should include the name of
            the manufacturer, the product name and the version
            of the hardware interface."
        ::= { ifEntry 2 }

    ifType OBJECT-TYPE
        SYNTAX  INTEGER {
            other(1),
            regular1822(2),
            hdh1822(3),
            ddnX25(4),
            rfc877x25(5),
            ethernetCsmacd(6),
            iso88023Csmacd(7),
            iso88024TokenBus(8),
            iso88025TokenRing(9),
            iso88026Man(10),
            starLan(11),
            proteon10Mbit(12),
            proteon80Mbit(13),
            hyperchannel(14),
            fddi(15),
            lapb(16),
            sdlc(17),
            ds1(18),
            e1(19),
            basicISDN(20),
            primaryISDN(21),
            propPointToPointSerial(22),
            ppp(23),
            softwareLoopback(24),
            eon(25),
            ethernet3Mbit(26),
            nsip(27),
            slip(28),
            ultra(29),
            ds3(30),
            sip(31),
            frameRelay(32),
            rs232(33),
            para(34),
            arcnet(35),
            arcnetPlus(36),
            atm(37),
            miox25(38),
            sonet(39),
            x25ple(40),
            iso88022llc(41),
            localTalk(42),
            smdsDxi(43),
            frameRelayService(44),
            v35(45),
            hssi(46),
            hippi(47),
            modem(48),
            aal5(49),
            sonetPath(50),
            sonetVT(51),
            smdsIcip(52),
            propVirtual(53),
            propMultiplexor(54),
            ieee80212(55),
            fibreChannel(56),
            hippiInterface(57),
            frameRelayInterconnect(58),
            aflane8023(59),
            aflane8025(60),
            cctEmul(61),
            fastEther(62),
            isdn(63),
            v11(64),
            v36(65),
            g703at64k(66),
            g703at2mb(67),
            qllc(68),
            fastEtherFX(69),
            channel(70),
            ieee80211(71),
            ibm370parChan(72),
            escon(73),
            dlsw(74),
            isdns(75),
            isdnu(76),
            lapd(77),
            ipSwitch(78),
            rsrb(79),
            atmLogical(80),
            ds0(81),
            ds0Bundle(82),
            bsc(83),
            async(84),
            cnr(85),
            iso88025Dtr(86),
            eplrs(87),
            arap(88),
            propCnls(89),
            hostPad(90),
            termPad(91),
            frameRelayMPI(92),
            x213(93),
            adsl(94),
            radsl(95),
            sdsl(96),
            vdsl(97),
            iso88025CRFPInt(98),
            myrinet(99),
            voiceEM(100),
            voiceFXO(101),
            voiceFXS(102),
            voiceEncap(103),
            voiceOverIp(104),
            atmDxi(105),
            atmFuni(106),
            atmIma (107),
            pppMultilinkBundle(108),
            ipOverCdlc (109),
            ipOverClaw (110),
            stackToStack (111),
            virtualIpAddress (112),
            mpc (113),
            ipOverAtm (114),
            iso88025Fiber (115),
            tdlc (116),
            gigabitEthernet (117),
            hdlc (118),
            lapf (119),
            v37 (120),
            x25mlp (121),
            x25huntGroup (122),
            trasnpHdlc (123),
            interleave (124),
            fast (125),
            ip (126),
            docsCableMaclayer (127),
            docsCableDownstream (128),
            docsCableUpstream (129),
            a12MppSwitch (130),
            tunnel (131),
            coffee (132),
            ces (133),
            atmSubInterface (134),
            l2vlan (135),
            l3ipvlan (136),
            l3ipxvlan (137),
            digitalPowerline (138),
            mediaMailOverIp (139),
            dtm (140),
            dcn (141),
            ipForward (142),
            msdsl (143),
            ieee1394 (144),
            if-gsn (145),
            dvbRccMacLayer (146),
            dvbRccDownstream (147),
            dvbRccUpstream (148),
            atmVirtual (149),
            mplsTunnel (150),
            srp (151),
            voiceOverAtm (152),
            voiceOverFrameRelay (153),
            idsl (154),
            compositeLink (155),
            ss7SigLink (156),
            propWirelessP2P (157),
            frForward (158),
            rfc1483 (159),
            usb (160),
            ieee8023adLag (161),
            bgppolicyaccounting (162),
            frf16MfrBundle (163),
            h323Gatekeeper (164),
            h323Proxy (165),
            mpls (166),
            mfSigLink (167),
            hdsl2 (168),
            shdsl (169),
            ds1FDL (170),
            pos (171),
            dvbAsiIn (172),
            dvbAsiOut (173),
            plc (174),
            nfas (175),
            tr008 (176),
            gr303RDT (177),
            gr303IDT (178),
            isup (179),
            propDocsWirelessMaclayer (180),
            propDocsWirelessDownstream (181),
            propDocsWirelessUpstream (182),
            hiperlan2 (183),
            propBWAp2Mp (184),
            sonetOverheadChannel (185),
            digitalWrapperOverheadChannel (186),
            aal2 (187),
            radioMAC (188),
            atmRadio (189),
            imt (190),
            mvl (191),
            reachDSL (192),
            frDlciEndPt (193),
            atmVciEndPt (194),
            opticalChannel (195),
            opticalTransport (196),
            propAtm (197),
            voiceOverCable (198),
            infiniband (199),
            teLink (200),
            q2931 (201),
            virtualTg (202),
            sipTg (203),
            sipSig (204),
            docsCableUpstreamChannel (205),
            econet (206),
            pon155 (207),
            pon622 (208),
            bridge (209),
            linegroup (210),
            voiceEMFGD (211),
            voiceFGDEANA (212),
            voiceDID (213),
            mpegTransport (214),
            sixToFour (215),
            gtp (216),
            pdnEtherLoop1 (217),
            pdnEtherLoop2 (218),
            opticalChannelGroup (219),
            homepna (220),
            gfp (221),
            ciscoISLvlan (222),
            actelisMetaLOOP (223),
            fcipLink (224),
            rpr (225),
            qam (226),                       -- RF Qam Interface
            lmp (227),                       -- Link Management Protocol
            cblVectaStar (228),              -- Cambridge Broadband Limited VectaStar
            docsCableMCmtsDownstream (229),  -- CATV Modular CMTS Downstream Interface
            adsl2 (230),                     -- Asymmetric Digital Subscriber Loop Version 2
                                             -- (DEPRECATED/OBSOLETED - please use adsl2plus 238 instead)
            macSecControlledIF (231),        -- MACSecControlled
            macSecUncontrolledIF (232),      -- MACSecUncontrolled
            aviciOpticalEther (233),         -- Avici Optical Ethernet Aggregate
            atmbond (234),                   -- atmbond
            voiceFGDOS (235),                -- voice FGD Operator Services
            mocaVersion1 (236),              -- MultiMedia over Coax Alliance (MoCA) Interface
                                             -- as documented in information provided privately to IANA
            ieee80216WMAN (237),             -- IEEE 802.16 WMAN interface
            adsl2plus (238),                 -- Asymmetric Digital Subscriber Loop Version 2,
                                             -- Version 2 Plus and all variants
            dvbRcsMacLayer (239),            -- DVB-RCS MAC Layer
            dvbTdm (240),                    -- DVB Satellite TDM
            dvbRcsTdma (241)                 -- DVB-RCS TDMA
        }
        ACCESS  read-only
        STATUS  mandatory
        DESCRIPTION
            "The type of interface, distinguished according to
            the physical/link protocol(s) immediately `below'
            the network layer in the protocol stack."
        ::= { ifEntry 3 }

    ifMtu OBJECT-TYPE
        SYNTAX  INTEGER
        ACCESS  read-only
        STATUS  mandatory
        DESCRIPTION
            "The size of the largest datagram which can be
            sent/received on the interface, specified in
            octets.  For interfaces that are used for
            transmitting network datagrams, this is the size
            of the largest network datagram that can be sent
            on the interface."
        ::= { ifEntry 4 }

    ifSpeed OBJECT-TYPE
        SYNTAX  Gauge
        ACCESS  read-only
        STATUS  mandatory
        DESCRIPTION
            "An estimate of the interface's current bandwidth
            in bits per second.  For interfaces which do not
            vary in bandwidth or for those where no accurate
            estimation can be made, this object should contain
            the nominal bandwidth."
        ::= { ifEntry 5 }

    ifPhysAddress OBJECT-TYPE
        SYNTAX  PhysAddress
        ACCESS  read-only
        STATUS  mandatory
        DESCRIPTION
            "The interface's address at the protocol layer
            immediately `below' the network layer in the
            protocol stack.  For interfaces which do not have
            such an address (e.g., a serial line), this object
            should contain an octet string of zero length."
        ::= { ifEntry 6 }

    ifAdminStatus OBJECT-TYPE
        SYNTAX  INTEGER
        {
            up(1),       -- ready to pass packets
            down(2),
            testing(3)   -- in some test mode
        }
        ACCESS  read-write
        STATUS  mandatory
        DESCRIPTION
            "The desired state of the interface. The
            testing(3) state indicates that no operational
            packets can be passed."
        ::= { ifEntry 7 }

    ifOperStatus OBJECT-TYPE
        SYNTAX  INTEGER
        {
            up(1),            -- ready to pass packets
            down(2),
            testing(3),       -- in some test mode
            unknown(4),       -- status can not be determined for some reason.
            dormant(5),
            notPresent(6),    -- some component is missing
            lowerLayerDown(7) -- down due to state of lower-layer interface(s)
        }
        ACCESS  read-only
        STATUS  mandatory
        DESCRIPTION
            "The current operational state of the interface.
            The testing(3) state indicates that no operational
            packets can be passed."
        ::= { ifEntry 8 }

    ifLastChange OBJECT-TYPE
        SYNTAX  TimeTicks
        ACCESS  read-only
        STATUS  mandatory
        DESCRIPTION
            "The value of sysUpTime at the time the interface
            entered its current operational state.  If the
            current state was entered prior to the last re-
            initialization of the local network management
            subsystem, then this object contains a zero
            value."
        ::= { ifEntry 9 }

    ifInOctets OBJECT-TYPE
        SYNTAX  Counter
        ACCESS  read-only
        STATUS  mandatory
        DESCRIPTION
            "The total number of octets received on the
            interface, including framing characters."
        ::= { ifEntry 10 }

    ifInUcastPkts OBJECT-TYPE
        SYNTAX  Counter
        ACCESS  read-only
        STATUS  mandatory
        DESCRIPTION
            "The number of subnetwork-unicast packets
            delivered to a higher-layer protocol."
        ::= { ifEntry 11 }

    ifInNUcastPkts OBJECT-TYPE
        SYNTAX  Counter
        ACCESS  read-only
        STATUS  mandatory
        DESCRIPTION
            "The number of non-unicast (i.e., subnetwork-
            broadcast or subnetwork-multicast) packets
            delivered to a higher-layer protocol."
        ::= { ifEntry 12 }

    ifInDiscards OBJECT-TYPE
        SYNTAX  Counter
        ACCESS  read-only
        STATUS  mandatory
        DESCRIPTION
            "The number of inbound packets which were chosen
            to be discarded even though no errors had been
            detected to prevent their being deliverable to a
            higher-layer protocol.  One possible reason for
            discarding such a packet could be to free up
            buffer space."
        ::= { ifEntry 13 }

    ifInErrors OBJECT-TYPE
        SYNTAX  Counter
        ACCESS  read-only
        STATUS  mandatory
        DESCRIPTION
            "The number of inbound packets that contained
            errors preventing them from being deliverable to a
            higher-layer protocol."
        ::= { ifEntry 14 }

    ifInUnknownProtos OBJECT-TYPE
        SYNTAX  Counter
        ACCESS  read-only
        STATUS  mandatory
        DESCRIPTION
            "The number of packets received via the interface
            which were discarded because of an unknown or
            unsupported protocol."
        ::= { ifEntry 15 }

    ifOutOctets OBJECT-TYPE
        SYNTAX  Counter
        ACCESS  read-only
        STATUS  mandatory
        DESCRIPTION
            "The total number of octets transmitted out of the
            interface, including framing characters."
        ::= { ifEntry 16 }

    ifOutUcastPkts OBJECT-TYPE
        SYNTAX  Counter
        ACCESS  read-only
        STATUS  mandatory
        DESCRIPTION
            "The total number of packets that higher-level
            protocols requested be transmitted to a
            subnetwork-unicast address, including those that
            were discarded or not sent."
        ::= { ifEntry 17 }

    ifOutNUcastPkts OBJECT-TYPE
        SYNTAX  Counter
        ACCESS  read-only
        STATUS  mandatory
        DESCRIPTION
            "The total number of packets that higher-level
            protocols requested be transmitted to a non-
            unicast (i.e., a subnetwork-broadcast or
            subnetwork-multicast) address, including those
            that were discarded or not sent."
        ::= { ifEntry 18 }

    ifOutDiscards OBJECT-TYPE
        SYNTAX  Counter
        ACCESS  read-only
        STATUS  mandatory
        DESCRIPTION
            "The number of outbound packets which were chosen
            to be discarded even though no errors had been
            detected to prevent their being transmitted.  One
            possible reason for discarding such a packet could
            be to free up buffer space."
        ::= { ifEntry 19 }

    ifOutErrors OBJECT-TYPE
        SYNTAX  Counter
        ACCESS  read-only
        STATUS  mandatory
        DESCRIPTION
            "The number of outbound packets that could not be
            transmitted because of errors."
        ::= { ifEntry 20 }

    ifOutQLen OBJECT-TYPE
        SYNTAX  Gauge
        ACCESS  read-only
        STATUS  mandatory
        DESCRIPTION
            "The length of the output packet queue (in
            packets)."
        ::= { ifEntry 21 }

    ifSpecific OBJECT-TYPE
        SYNTAX  OBJECT IDENTIFIER
        ACCESS  read-only
        STATUS  mandatory
        DESCRIPTION
            "A reference to MIB definitions specific to the
            particular media being used to realize the
            interface.  For example, if the interface is
            realized by an ethernet, then the value of this
            object refers to a document defining objects
            specific to ethernet.  If this information is not
            present, its value should be set to the OBJECT
            IDENTIFIER { 0 0 }, which is a syntatically valid
            object identifier, and any conformant
            implementation of ASN.1 and BER must be able to
            generate and recognize this value."
        ::= { ifEntry 22 }

--------------------------------------------------------------------------------
--------------------------------------------------------------------------------
--                              Node Summaries                                --
--------------------------------------------------------------------------------
--------------------------------------------------------------------------------

    -- 1.3.6.1.4.enterprises(1).ExoticCandy-MIB(59097).EC-General-Devices(1)
    Devices-Node-Summary OBJECT-TYPE
        SYNTAX      OCTET STRING
        MAX-ACCESS  not-accessible
        STATUS      current
        DESCRIPTION
            "This folder contains all the (hardware) devices programmed
             by Mohammad Kazem Azizollahi.
             It will be used as a root for the devices' MIB trees."
        ::= { EC-General-Devices 0 }

    -- 1.3.6.1.4.enterprises(1).ExoticCandy-MIB(59097).EC-General-Software(2)
    Software-Node-Summary OBJECT-TYPE
        SYNTAX      OCTET STRING
        MAX-ACCESS  not-accessible
        STATUS      current
        DESCRIPTION
            "This folder contains all the (hardware) softwares written
             by Mohammad Kazem Azizollahi.
             It will be used as a root for the softwares' MIB trees."
        ::= { EC-General-Software 0 }

    -- 1.3.6.1.4.enterprises(1).ExoticCandy-MIB(59097).EC-Generic-Traps(3)
    Traps-Node-Summary OBJECT-TYPE
        SYNTAX      OCTET STRING
        MAX-ACCESS  not-accessible
        STATUS      current
        DESCRIPTION
            "This folder contains all the generic traps which are shared
             between all the devices."
        ::= { EC-Generic-Traps 0 }

    -- 1.3.6.1.4.enterprises(1).ExoticCandy-MIB(59097).EC-Experimental(4)
    Experimental-Node-Summary OBJECT-TYPE
        SYNTAX      OCTET STRING
        MAX-ACCESS  not-accessible
        STATUS      current
        DESCRIPTION
            "This folder is used for experimental usages only."
        ::= { EC-Experimental 0 }

    -- 1.3.6.1.4.enterprises(1).ExoticCandy-MIB(59097).EC-Information(5)
    Information-Node-Summary OBJECT-TYPE
        SYNTAX      OCTET STRING
        MAX-ACCESS  not-accessible
        STATUS      current
        DESCRIPTION
            "This folder is used for support information."
        ::= { EC-Information 0 }

--------------------------------------------------------------------------------
--------------------------------------------------------------------------------
--                         End of Tree Placeholders                           --
--------------------------------------------------------------------------------
--------------------------------------------------------------------------------

    --End-Of-Supported-Tree       OBJECT IDENTIFIER ::= { member-body     0 }
    --End-Of-Supported-Tree       OBJECT IDENTIFIER ::= { directory       0 }
    --End-Of-Supported-Tree       OBJECT IDENTIFIER ::= { experimental    0 }
    --End-Of-Supported-Tree       OBJECT IDENTIFIER ::= { security        0 }
    --End-Of-Supported-Tree       OBJECT IDENTIFIER ::= { mail            0 }
    --End-Of-Supported-Tree       OBJECT IDENTIFIER ::= { features        0 }

END
